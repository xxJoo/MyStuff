;;; <LISPDOC>
;;; <SUBR>(AutoCAD_init)</SUBR>
;;; <DESC>PreSettings for a new opened dwg file</DESC>
;;; <RET>Nothing</RET>
;;; </LISPDOC>

; 



(prompt "\n***** << AutoCAD_init.lsp 加载开始>> *****\n")

; -------------------------------------------------------
; 添加path变量到搜索路径  加载其他模块
(load "C_MarkPoint.lsp") 
(load "C_MarkTube.lsp")
(load "C_Bolt.lsp")
(load "C_Length.lsp")
(load "C_LineSetDivide.lsp")
(load "C_Calculation.lsp")
(load "C_OverlapRate.lsp")
(load "C_GL.lsp")
(load "VLX_Bitch_5.8.VLX") ; 执行不成功

; -------------------------------------------------------


; -------------------------------------------------------
; 选项设置
; -------------------------------------------------------

(prompt "\n***** << AutoCAD_init.lsp 选项设置>> *****\n")

(if (= (getvar "ACADVER") "20.1s (LMS Tech)") ; CAD 2016
    (progn
        (setvar "startmode" 0)   ; 无开始窗口 CAD2012 无此命令
        (setvar "COLORTHEME" 0)  ; 配色方案 暗 CAD2012 无此命令
    )
    "no."
)
(setvar "dimassoc" 1)      ; 标注不关联
(setvar "shortcutmenu" 0)  ; 不适用右键
(setvar "PICKBOX" 8)       ; 拾取框大小
(setvar "PICKSTYLE" 0)     ; 无对象编组选择
; (FILETAB)                ; 显示文件选项卡
; (FILETABCLOSE)           ; 不显示文件选项卡
(setvar "CURSORSIZE" 100)  ; 十字光标大小
(setvar "XDWGFADECTL" 50)  ; 外部参照显示透明度
(setvar "XFADECTL" 70)     ; 在位编辑和注释性图示
(setvar "SAVETIME" 30)     ; 自动保存时间
(setvar "ISAVEBAK" 0)      ; 每次保存均创建备份 否
(setvar "LWDEFAULT" 25)    ; 0.25 mm 线宽
; -------------------------------------------------------


; -------------------------------------------------------
; 点设置
; -------------------------------------------------------

(prompt "\n***** << AutoCAD_init.lsp  点设置 >> *****\n")

(setvar "PDMODE" 35)       ; 点的模式为 35
(setvar "PDSIZE" 200)      ; 点的大小为 200
(setvar "OSMODE" 5375)     ; 对象捕捉
; -------------------------------------------------------


; -------------------------------------------------------
; 自动保存为2004格式
; -------------------------------------------------------

(prompt "\n**  AutoCAD_init.lsp 自动保存为2004格式 **\n")



; -------------------------------------------------------





; -------------------------------------------------------
; 电子传递设置
; -------------------------------------------------------


; -------------------------------------------------------




; -------------------------------------------------------
; 文字样式
; -------------------------------------------------------

(prompt "\n***** << AutoCAD_init.lsp 文字样式>> *****\n")


; -------------------------------------------------------




; -------------------------------------------------------
; 标注样式
; -------------------------------------------------------


(prompt "\n***** << AutoCAD_init.lsp 标注样式>> *****\n")



; -------------------------------------------------------





(prompt "\n***** << AutoCAD_init.lsp 加载完毕>> *****\n")
