; 





; 选项设置
; -------------------------------------------------------
(setvar "dimassoc" 0)      ; 标注不关联
(setvar "shortcutmenu" 0)  ; 不适用右键
(setvar "startmode" 0)     ; 无开始窗口
(setvar "PICKBOX" 8)       ; 拾取框大小
(setvar "PICKSTYLE" 0)     ; 五对象编组选择
(setvar "COLORTHEME" 0)    ; 配色方案 暗
(FILETAB)                  ; 显示文件选项卡
; (FILETABCLOSE)           ; 不显示文件选项卡
(setvar "CURSORSIZE" 100)  ; 十字光标大小
(setvar "XDWGFADECTL" 50)  ; 外部参照显示透明度
(setvar "XFADECTL" 70)     ; 在位编辑和注释性图示
(setvar "SAVETIME" 30)     ; 自动保存时间
(setvar "ISAVEBAK" 0)      ; 每次保存均创建备份 否
(setvar "SHORTCUTMENU" 0)  ; 绘图区域中使用快捷菜单
(setvar "DIMASSOC" 2)      ; 使新标注与对象关联
(setvar "LWDEFAULT" 25)    ; 0.25 mm 线宽
; -------------------------------------------------------

; 点设置
; -------------------------------------------------------
(setvar "PDMODE" 35)       ; 点的模式为 35
(setvar "PDSIZE" 200)      ; 点的大小为 200
(setvar "OSMODE" 5375)     ; 对象捕捉
(setvar "ISAVEBAK" 0)      ; 保存时不建立副本


; 自动保存为2004格式
; -------------------------------------------------------

; 电子传递设置
; -------------------------------------------------------

; 文字样式
; -------------------------------------------------------



(prompt "********** << AutoCAD_init.lsp >> **********\n")
